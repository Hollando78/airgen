# AIRGen System Requirements Specification
AIRGen System Requirements exported from SYSTEM_REQUIREMENTS.md

# Specification: AIRGen System Requirements Specification
- Title: AIRGen System Requirements Specification

## REQ-SYS-001: User Login
The system shall authenticate users via email and password credentials using Argon2id password hashing.
- Pattern: Event-driven (WHEN user submits credentials)
- Verification: Test
- Priority: Must Have
- Source: DDD §3.3.3, §5.1.1, §7.1

## REQ-SYS-002: JWT Token Generation
When a user successfully authenticates, the system shall generate a JWT token containing user ID, email, roles, and tenant slugs with a 24-hour expiration.
- Pattern: Event-driven (WHEN authentication succeeds)
- Verification: Test
- Priority: Must Have
- Source: DDD §3.3.3, §6.1.3, §7.1

## REQ-SYS-003: Multi-Factor Authentication
The system shall support optional TOTP-based 2FA verification for users with totpEnabled set to true.
- Pattern: State-driven (WHILE 2FA is enabled)
- Verification: Test
- Priority: Should Have
- Source: DDD §3.3.3, §5.1.1, §7.1

## REQ-SYS-004: Token Validation
The system shall validate JWT tokens on every authenticated request, verifying signature and expiration.
- Pattern: Ubiquitous (for all authenticated requests)
- Verification: Test
- Priority: Must Have
- Source: DDD §3.3.3, §4.1.1, §7.1

## REQ-SYS-005: Token Refresh
When an access token expires, the system shall allow token refresh using a valid refresh token.
- Pattern: Event-driven (WHEN token expires)
- Verification: Test
- Priority: Must Have
- Source: DDD §3.3.3, §9.8

## REQ-SYS-006: Role-Based Access Control
The system shall enforce role-based permissions for Admin, Author, Reviewer, and User roles.
- Pattern: Ubiquitous (for all operations)
- Verification: Test
- Priority: Must Have
- Source: DDD §4.1.1, §7.2

## REQ-SYS-007: Multi-Tenant User Association
The system shall allow users to belong to multiple tenants via the tenantSlugs JWT claim.
- Pattern: Ubiquitous
- Verification: Test
- Priority: Must Have
- Source: DDD §5.1.1, §6.1.3, §7.2

## REQ-SYS-008: User Last Login Tracking
The system shall update the lastLoginAt timestamp when a user successfully authenticates.
- Pattern: Event-driven (WHEN login succeeds)
- Verification: Test
- Priority: Should Have
- Source: DDD §5.1.1

## REQ-SYS-009: User Password Security
The system shall store user passwords as Argon2id hashes, never storing plaintext passwords.
- Pattern: Ubiquitous
- Verification: Inspection
- Priority: Must Have
- Source: DDD §5.1.1, §7.1, §7.3

## REQ-SYS-010: User Session Logout
The system shall provide a logout endpoint that invalidates the current user session.
- Pattern: Event-driven (WHEN user logs out)
- Verification: Test
- Priority: Should Have
- Source: DDD §6.1.2

## REQ-SYS-011: Create Requirement
The system shall create requirements with text, pattern, verification method, and metadata properties.
- Pattern: Event-driven (WHEN user creates requirement)
- Verification: Test
- Priority: Must Have
- Source: DDD §2.3.1, §3.3.1, §6.1.2

## REQ-SYS-012: Dual Persistence
When creating a requirement, the system shall write both to Neo4j (metadata) and file system (Markdown) in a single transaction.
- Pattern: Event-driven (WHEN requirement created)
- Verification: Test
- Priority: Must Have
- Source: DDD §2.1, §3.3.1, §9.1

## REQ-SYS-013: Requirement Reference Generation
The system shall generate unique requirement references in the format REQ-<KEY>-<NNN> where KEY is the project key and NNN is an auto-incremented number.
- Pattern: Event-driven (WHEN requirement created)
- Verification: Test
- Priority: Must Have
- Source: DDD §5.1.1, §5.2

## REQ-SYS-014: List Requirements
The system shall retrieve all requirements for a tenant and project, filtered by tenant context.
- Pattern: Ubiquitous
- Verification: Test
- Priority: Must Have
- Source: DDD §6.1.2, §7.2

## REQ-SYS-015: Update Requirement
The system shall allow updating requirement text, pattern, verification method, tags, and custom attributes.
- Pattern: Event-driven (WHEN user updates requirement)
- Verification: Test
- Priority: Must Have
- Source: DDD §2.3.1, §6.1.2

## REQ-SYS-016: Delete Requirement
The system shall support soft deletion of requirements by setting the deleted flag to true.
- Pattern: Event-driven (WHEN user deletes requirement)
- Verification: Test
- Priority: Must Have
- Source: DDD §5.1.1, §6.1.2

## REQ-SYS-017: Archive Requirement
The system shall allow archiving requirements by setting the archived flag to true.
- Pattern: Event-driven (WHEN user archives requirement)
- Verification: Test
- Priority: Must Have
- Source: DDD §2.3.1, §5.1.1, §6.1.2

## REQ-SYS-018: Unarchive Requirement
The system shall allow unarchiving requirements by setting the archived flag to false.
- Pattern: Event-driven (WHEN user unarchives requirement)
- Verification: Test
- Priority: Must Have
- Source: DDD §2.3.1, §6.1.2

## REQ-SYS-019: Requirement Version History
The system shall create immutable RequirementVersion snapshots for every requirement change.
- Pattern: Event-driven (WHEN requirement changes)
- Verification: Test
- Priority: Must Have
- Source: DDD §2.3.1, §5.1.1, §6.1.2

## REQ-SYS-020: Version Number Auto-Increment
The system shall auto-increment version numbers (1, 2, 3...) for each requirement's version history.
- Pattern: Event-driven (WHEN version created)
- Verification: Test
- Priority: Must Have
- Source: DDD §5.1.1

## REQ-SYS-021: Version Change Tracking
The system shall record changeType (created|updated|archived|restored|deleted), changedBy, and timestamp for each version.
- Pattern: Event-driven (WHEN version created)
- Verification: Test
- Priority: Must Have
- Source: DDD §5.1.1

## REQ-SYS-022: Version Snapshot Completeness
The system shall store complete snapshots of requirement state in each version, including text, pattern, verification, QA scores, tags, and attributes.
- Pattern: Ubiquitous (for all versions)
- Verification: Test
- Priority: Must Have
- Source: DDD §5.1.1

## REQ-SYS-023: Get Version History
The system shall retrieve the complete version history for a requirement ordered by version number.
- Pattern: Event-driven (WHEN user requests history)
- Verification: Test
- Priority: Must Have
- Source: DDD §6.1.2

## REQ-SYS-024: Version Diff
The system shall compute and return differences between two requirement versions specified by version numbers.
- Pattern: Event-driven (WHEN user requests diff)
- Verification: Test
- Priority: Should Have
- Source: DDD §2.3.1, §6.1.2

## REQ-SYS-025: Restore Previous Version
The system shall allow restoring a requirement to a previous version, creating a new version with the restored content.
- Pattern: Event-driven (WHEN user restores version)
- Verification: Test
- Priority: Should Have
- Source: DDD §6.1.2

## REQ-SYS-026: Content Hash Generation
The system shall generate SHA-256 content hashes for requirements to enable drift detection.
- Pattern: Event-driven (WHEN requirement created/updated)
- Verification: Test
- Priority: Should Have
- Source: DDD §5.1.1

## REQ-SYS-027: Duplicate Detection
The system shall detect duplicate requirements using content hash comparison.
- Pattern: Event-driven (WHEN requirement created)
- Verification: Test
- Priority: Should Have
- Source: DDD §2.3.1, §5.1.1

## REQ-SYS-028: Custom Attributes
The system shall support project-specific custom attributes stored as JSON objects on requirements.
- Pattern: Ubiquitous
- Verification: Test
- Priority: Should Have
- Source: DDD §5.1.1, §10.1

## REQ-SYS-029: Requirement Tags
The system shall support multiple tags per requirement for categorization and filtering.
- Pattern: Ubiquitous
- Verification: Test
- Priority: Should Have
- Source: DDD §5.1.1

## REQ-SYS-030: Creator and Updater Tracking
The system shall record createdBy and updatedBy user identifiers for requirements.
- Pattern: Event-driven (WHEN requirement created/updated)
- Verification: Test
- Priority: Should Have
- Source: DDD §5.1.1

## REQ-SYS-031: Timestamp Tracking
The system shall record createdAt and updatedAt timestamps for all requirements.
- Pattern: Event-driven (WHEN requirement created/updated)
- Verification: Test
- Priority: Must Have
- Source: DDD §5.1.1

## REQ-SYS-032: EARS Pattern Support
The system shall support EARS requirement patterns: ubiquitous, event, state, unwanted, and optional.
- Pattern: Ubiquitous
- Verification: Test
- Priority: Must Have
- Source: DDD §5.1.1, §6.1.2

## REQ-SYS-033: Verification Method Support
The system shall support verification methods: Test, Analysis, Inspection, and Demonstration.
- Pattern: Ubiquitous
- Verification: Test
- Priority: Must Have
- Source: DDD §5.1.1, §6.1.2

## REQ-SYS-034: Generate Requirement Drafts
When a user requests requirement drafts, the system shall generate both heuristic-based and LLM-based candidates.
- Pattern: Event-driven (WHEN user requests drafts)
- Verification: Test
- Priority: Must Have
- Source: DDD §2.3.2, §3.3.1, §6.1.2

## REQ-SYS-035: Heuristic Draft Generation
The system shall generate EARS pattern-based heuristic drafts without requiring external AI services.
- Pattern: Event-driven (WHEN drafts requested)
- Verification: Test
- Priority: Must Have
- Source: DDD §2.3.2, §4.1.3, §9.6

## REQ-SYS-036: LLM Draft Generation
When LLM services are enabled, the system shall generate AI-powered requirement drafts using the configured LLM provider.
- Pattern: Event-driven (WHEN drafts requested and LLM enabled)
- Verification: Test
- Priority: Should Have
- Source: DDD §2.3.2, §3.3.1, §4.1.3

## REQ-SYS-037: OpenAI Provider Support
The system shall support OpenAI (GPT-4o, GPT-4o-mini) as an LLM provider when OPENAI_API_KEY is configured.
- Pattern: State-driven (WHILE OpenAI configured)
- Verification: Test
- Priority: Should Have
- Source: DDD §4.1.3

## REQ-SYS-038: Self-Hosted LLM Support
The system shall support self-hosted LLM providers (Ollama, vLLM) when OLLAMA_API_BASE or VLLM_API_BASE is configured.
- Pattern: State-driven (WHILE self-hosted LLM configured)
- Verification: Test
- Priority: Should Have
- Source: DDD §4.1.3

## REQ-SYS-039: LLM Disabled Mode
The system shall operate in disabled mode (heuristics only) when no LLM provider is configured.
- Pattern: State-driven (WHILE no LLM configured)
- Verification: Test
- Priority: Must Have
- Source: DDD §4.1.3

## REQ-SYS-040: LLM Provider Selection
The system shall select LLM providers in order of priority: Ollama, vLLM, OpenAI, Disabled.
- Pattern: Ubiquitous (at startup)
- Verification: Test
- Priority: Must Have
- Source: DDD §4.1.3

## REQ-SYS-041: LLM Error Handling
When LLM generation fails, the system shall gracefully fall back to heuristic drafts only.
- Pattern: Unwanted (IF LLM fails)
- Verification: Test
- Priority: Must Have
- Source: DDD §4.1.3

## REQ-SYS-042: LLM Rate Limit Retry
When OpenAI rate limits are encountered, the system shall retry with exponential backoff.
- Pattern: Event-driven (WHEN rate limited)
- Verification: Test
- Priority: Should Have
- Source: DDD §4.1.3

## REQ-SYS-043: LLM Timeout Protection
The system shall timeout LLM requests after 30 seconds for text generation and 60 seconds for vision requests.
- Pattern: Ubiquitous (for all LLM calls)
- Verification: Test
- Priority: Must Have
- Source: DDD §4.1.3

## REQ-SYS-044: AI Image Analysis
The system shall support vision API analysis of image attachments using the configured LLM provider.
- Pattern: Event-driven (WHEN image analyzed)
- Verification: Test
- Priority: Should Have
- Source: DDD §4.1.3

## REQ-SYS-045: AI Usage Audit Logging
The system shall log all AI requests with provider, model, timestamp, and user for compliance auditing.
- Pattern: Event-driven (WHEN AI used)
- Verification: Test
- Priority: Must Have
- Source: DDD §2.3.9, §4.1.3

## REQ-SYS-046: Draft Candidate Review
The system shall present draft candidates to users with QA scores for review and selection.
- Pattern: Event-driven (WHEN drafts generated)
- Verification: Demonstration
- Priority: Must Have
- Source: DDD §2.3.2, §3.3.1

## REQ-SYS-047: Draft Acceptance Workflow
The system shall allow users to accept, edit, or reject draft candidates before creating requirements.
- Pattern: Event-driven (WHEN user selects draft)
- Verification: Test
- Priority: Must Have
- Source: DDD §2.3.2

## REQ-SYS-048: AI Image Generation
The system shall generate AI-powered images from requirement descriptions using vision AI.
- Pattern: Event-driven (WHEN user requests image)
- Verification: Test
- Priority: Could Have
- Source: DDD §2.3.6

## REQ-SYS-049: Context-Aware Image Creation
The system shall create images with awareness of requirement context and system architecture.
- Pattern: Event-driven (WHEN image generated)
- Verification: Demonstration
- Priority: Could Have
- Source: DDD §2.3.6

## REQ-SYS-050: Deterministic QA Scoring
The system shall score requirements using deterministic rule-based QA without AI dependencies.
- Pattern: Ubiquitous (for all requirements)
- Verification: Test
- Priority: Must Have
- Source: DDD §1.3, §3.2.3, §6.1.2

## REQ-SYS-051: ISO 29148 Alignment
The system shall apply QA rules aligned with ISO/IEC/IEEE 29148 standards.
- Pattern: Ubiquitous
- Verification: Analysis
- Priority: Must Have
- Source: DDD §1.1, §3.2.3

## REQ-SYS-052: Clarity Checking
The system shall detect ambiguous terms (e.g., "appropriate", "timely") in requirement text.
- Pattern: Ubiquitous (for all requirements)
- Verification: Test
- Priority: Must Have
- Source: DDD §3.2.3

## REQ-SYS-053: Completeness Checking
The system shall detect missing patterns or verification methods in requirements.
- Pattern: Ubiquitous (for all requirements)
- Verification: Test
- Priority: Must Have
- Source: DDD §3.2.3

## REQ-SYS-054: Consistency Checking
The system shall detect conflicting statements within requirement text.
- Pattern: Ubiquitous (for all requirements)
- Verification: Test
- Priority: Should Have
- Source: DDD §3.2.3

## REQ-SYS-055: Correctness Checking
The system shall detect grammar and formatting issues in requirement text.
- Pattern: Ubiquitous (for all requirements)
- Verification: Test
- Priority: Should Have
- Source: DDD §3.2.3

## REQ-SYS-056: Verifiability Checking
The system shall assess whether requirements contain measurable acceptance criteria.
- Pattern: Ubiquitous (for all requirements)
- Verification: Test
- Priority: Must Have
- Source: DDD §3.2.3

## REQ-SYS-057: QA Score Calculation
The system shall calculate QA scores from 0-100 based on detected issues.
- Pattern: Ubiquitous (for all requirements)
- Verification: Test
- Priority: Must Have
- Source: DDD §3.2.3, §5.1.1

## REQ-SYS-058: QA Verdict Assignment
The system shall assign QA verdicts (excellent|good|acceptable|poor) based on score thresholds.
- Pattern: Ubiquitous (for all requirements)
- Verification: Test
- Priority: Must Have
- Source: DDD §5.1.1

## REQ-SYS-059: Actionable Suggestions
The system shall provide actionable suggestions for improving requirement quality.
- Pattern: Ubiquitous (for all requirements)
- Verification: Test
- Priority: Must Have
- Source: DDD §3.2.3, §5.1.1

## REQ-SYS-060: QA Fix Suggestions
The system shall suggest specific fixes for detected QA issues via the apply-fix endpoint.
- Pattern: Event-driven (WHEN user requests fixes)
- Verification: Test
- Priority: Should Have
- Source: DDD §6.1.2

## REQ-SYS-061: Background QA Scorer
The system shall support background QA scoring workers for bulk quality analysis.
- Pattern: Event-driven (WHEN worker started)
- Verification: Test
- Priority: Should Have
- Source: DDD §2.3.1, §6.1.2

## REQ-SYS-062: QA Worker Control
The system shall provide endpoints to start, stop, and check status of QA scorer workers.
- Pattern: Event-driven (WHEN admin controls worker)
- Verification: Test
- Priority: Should Have
- Source: DDD §6.1.2

## REQ-SYS-063: Create Structured Document
The system shall create structured documents with sections for organizing requirements.
- Pattern: Event-driven (WHEN user creates document)
- Verification: Test
- Priority: Must Have
- Source: DDD §2.3.3, §6.1.2

## REQ-SYS-064: Upload Surrogate Document
The system shall allow uploading surrogate documents (PDF, Word, etc.) with metadata storage.
- Pattern: Event-driven (WHEN user uploads document)
- Verification: Test
- Priority: Must Have
- Source: DDD §2.3.3, §5.1.1, §6.1.2

## REQ-SYS-065: Document Slug Generation
The system shall generate unique slugs for documents within a project.
- Pattern: Event-driven (WHEN document created)
- Verification: Test
- Priority: Must Have
- Source: DDD §5.1.1, §6.1.2

## REQ-SYS-066: Document Short Codes
The system shall support short codes (e.g., "SRD", "URD") for document identification.
- Pattern: Ubiquitous
- Verification: Test
- Priority: Should Have
- Source: DDD §5.1.1

## REQ-SYS-067: Document Kind Classification
The system shall classify documents as either "structured" or "surrogate" kind.
- Pattern: Ubiquitous
- Verification: Test
- Priority: Must Have
- Source: DDD §5.1.1

## REQ-SYS-068: Surrogate File Storage
The system shall store surrogate document files in workspace/<tenant>/<project>/documents/<document-slug>/ directories.
- Pattern: Ubiquitous
- Verification: Inspection
- Priority: Must Have
- Source: DDD §5.2

## REQ-SYS-069: Surrogate File Metadata
The system shall store originalFileName, storedFileName, mimeType, fileSize, and storagePath for surrogate documents.
- Pattern: Ubiquitous (for surrogates)
- Verification: Test
- Priority: Must Have
- Source: DDD §5.1.1

## REQ-SYS-070: Document Sections
The system shall support hierarchical document sections for organizing structured documents.
- Pattern: Ubiquitous (for structured docs)
- Verification: Test
- Priority: Should Have
- Source: DDD §2.3.3, §5.1

## REQ-SYS-071: Document-Requirement Linking
The system shall link requirements to documents and document sections via CONTAINS relationships.
- Pattern: Ubiquitous
- Verification: Test
- Priority: Must Have
- Source: DDD §2.3.3, §5.1.2

## REQ-SYS-072: Hierarchical Folder Organization
The system shall organize documents in hierarchical folders.
- Pattern: Ubiquitous
- Verification: Test
- Priority: Should Have
- Source: DDD §2.3.3, §5.1

## REQ-SYS-073: List Documents
The system shall retrieve all documents for a tenant and project.
- Pattern: Ubiquitous
- Verification: Test
- Priority: Must Have
- Source: DDD §6.1.2

## REQ-SYS-074: Get Document Metadata
The system shall retrieve document metadata by slug.
- Pattern: Event-driven (WHEN user views document)
- Verification: Test
- Priority: Must Have
- Source: DDD §6.1.2

## REQ-SYS-075: Update Document
The system shall allow updating document name, description, and shortCode.
- Pattern: Event-driven (WHEN user updates document)
- Verification: Test
- Priority: Must Have
- Source: DDD §6.1.2

## REQ-SYS-076: Delete Document
The system shall support document deletion with cascade to related sections and files.
- Pattern: Event-driven (WHEN user deletes document)
- Verification: Test
- Priority: Must Have
- Source: DDD §6.1.2

## REQ-SYS-077: Create Trace Link
The system shall create typed trace links between requirements with relationship types.
- Pattern: Event-driven (WHEN user creates link)
- Verification: Test
- Priority: Must Have
- Source: DDD §2.3.4, §6.1.2

## REQ-SYS-078: Trace Link Types
The system shall support trace link types: SATISFIES, DERIVES, VERIFIES, IMPLEMENTS, REFINES, and CONFLICTS.
- Pattern: Ubiquitous
- Verification: Test
- Priority: Must Have
- Source: DDD §5.1.2

## REQ-SYS-079: Trace Link Metadata
The system shall store linkType, description, createdAt, and updatedAt for each trace link.
- Pattern: Ubiquitous
- Verification: Test
- Priority: Must Have
- Source: DDD §5.1.2

## REQ-SYS-080: List Trace Links
The system shall retrieve all trace links for a tenant and project.
- Pattern: Ubiquitous
- Verification: Test
- Priority: Must Have
- Source: DDD §3.3.2, §6.1.2

## REQ-SYS-081: Delete Trace Link
The system shall allow deletion of trace links by ID.
- Pattern: Event-driven (WHEN user deletes link)
- Verification: Test
- Priority: Must Have
- Source: DDD §6.1.2

## REQ-SYS-082: Graph-Based Link Suggestions
The system shall suggest trace links using graph algorithms analyzing text similarity, document relationships, and architecture connections.
- Pattern: Event-driven (WHEN user hovers over requirement)
- Verification: Test
- Priority: Should Have
- Source: DDD §2.3.4, §3.3.2, §6.1.2

## REQ-SYS-083: Broken Link Detection
The system shall detect broken trace links when requirements are deleted or archived.
- Pattern: Event-driven (WHEN requirement deleted/archived)
- Verification: Test
- Priority: Should Have
- Source: DDD §2.3.4

## REQ-SYS-084: Linkset Management
The system shall organize trace links into named linksets for grouped traceability.
- Pattern: Ubiquitous
- Verification: Test
- Priority: Should Have
- Source: DDD §2.3.4, §5.1

## REQ-SYS-085: Trace Link Caching
The system shall cache trace link queries in Redis with 5-minute TTL.
- Pattern: Ubiquitous (when Redis available)
- Verification: Test
- Priority: Should Have
- Source: DDD §3.3.2, §5.3

## REQ-SYS-086: Traceability Matrix View
The system shall render traceability matrices showing requirement relationships.
- Pattern: Event-driven (WHEN user views matrix)
- Verification: Demonstration
- Priority: Must Have
- Source: DDD §3.3.2, §6.2

## REQ-SYS-087: Create Architecture Diagram
The system shall create architecture diagrams with name, description, and view type.
- Pattern: Event-driven (WHEN user creates diagram)
- Verification: Test
- Priority: Must Have
- Source: DDD §2.3.5, §6.1.2

## REQ-SYS-088: Diagram View Types
The system shall support diagram views: block, internal, deployment, and requirements_schema.
- Pattern: Ubiquitous
- Verification: Test
- Priority: Must Have
- Source: DDD §5.1.1

## REQ-SYS-089: Reusable Block Library
The system shall maintain reusable ArchitectureBlockDefinition nodes shared across diagrams.
- Pattern: Ubiquitous
- Verification: Test
- Priority: Must Have
- Source: DDD §2.3.5, §5.1.1

## REQ-SYS-090: Block Kind Classification
The system shall classify blocks as: system, subsystem, component, actor, external, or interface.
- Pattern: Ubiquitous
- Verification: Test
- Priority: Must Have
- Source: DDD §5.1.1

## REQ-SYS-091: Block Ports
The system shall define ports on blocks with id, name, direction, and type properties.
- Pattern: Ubiquitous
- Verification: Test
- Priority: Must Have
- Source: DDD §2.3.5, §5.1.1

## REQ-SYS-092: Per-Diagram Block Placement
The system shall store block placement (positionX, positionY, sizeWidth, sizeHeight) on PLACES relationships per diagram.
- Pattern: Ubiquitous
- Verification: Test
- Priority: Must Have
- Source: DDD §3.3.4, §5.1.2, §9.10

## REQ-SYS-093: Per-Diagram Port Overrides
The system shall support per-diagram port visibility and positioning overrides stored as portOverrides JSON.
- Pattern: Ubiquitous
- Verification: Test
- Priority: Should Have
- Source: DDD §2.3.5, §5.1.2, §9.10

## REQ-SYS-094: Per-Diagram Styling
The system shall support per-diagram backgroundColor and borderColor for block placements.
- Pattern: Ubiquitous
- Verification: Test
- Priority: Should Have
- Source: DDD §2.3.5, §5.1.2

## REQ-SYS-095: Architecture Connectors
The system shall create connectors linking port instances with relationship labels.
- Pattern: Event-driven (WHEN user creates connector)
- Verification: Test
- Priority: Must Have
- Source: DDD §2.3.5, §5.1

## REQ-SYS-096: Diagram Rendering
The system shall transform Neo4j diagram data to ReactFlow format with nodes, edges, and viewport.
- Pattern: Event-driven (WHEN user views diagram)
- Verification: Test
- Priority: Must Have
- Source: DDD §3.3.4

## REQ-SYS-097: Diagram Interaction
The system shall support drag-and-drop, zoom, pan, and minimap interactions on diagrams.
- Pattern: Ubiquitous (in diagram view)
- Verification: Demonstration
- Priority: Must Have
- Source: DDD §4.2.1

## REQ-SYS-098: Diagram Context Menus
The system shall provide context menus for diagram elements.
- Pattern: Event-driven (WHEN user right-clicks)
- Verification: Demonstration
- Priority: Should Have
- Source: DDD §4.2.1

## REQ-SYS-099: Viewport Persistence
The system shall persist diagram viewport (zoom, position) per diagram.
- Pattern: Event-driven (WHEN viewport changes)
- Verification: Test
- Priority: Should Have
- Source: DDD §4.2.1

## REQ-SYS-100: Debounced Position Updates
The system shall debounce block position updates by 500ms to reduce API calls.
- Pattern: Event-driven (WHEN block dragged)
- Verification: Test
- Priority: Should Have
- Source: DDD §3.3.4

## REQ-SYS-101: Floating Diagram Windows
The system shall support floating, draggable, resizable windows for viewing multiple diagrams simultaneously.
- Pattern: Event-driven (WHEN user opens diagram)
- Verification: Demonstration
- Priority: Should Have
- Source: DDD §2.3.5, §4.2.2, §9.7

## REQ-SYS-102: Diagram Snapshot Capture
The system shall capture snapshots of diagrams for documentation purposes.
- Pattern: Event-driven (WHEN user captures snapshot)
- Verification: Test
- Priority: Should Have
- Source: DDD §2.3.5, §4.2.2

## REQ-SYS-103: Z-Index Window Management
The system shall manage z-index for floating windows to handle overlapping.
- Pattern: Event-driven (WHEN window focused)
- Verification: Test
- Priority: Should Have
- Source: DDD §4.2.2, §9.7

## REQ-SYS-104: List Diagrams
The system shall retrieve all diagrams for a tenant and project.
- Pattern: Ubiquitous
- Verification: Test
- Priority: Must Have
- Source: DDD §3.3.4, §6.1.2

## REQ-SYS-105: Update Diagram
The system shall allow updating diagram name, description, and view type.
- Pattern: Event-driven (WHEN user updates diagram)
- Verification: Test
- Priority: Must Have
- Source: DDD §6.1.2

## REQ-SYS-106: Delete Diagram
The system shall support diagram deletion with cascade to PLACES relationships.
- Pattern: Event-driven (WHEN user deletes diagram)
- Verification: Test
- Priority: Must Have
- Source: DDD §6.1.2

## REQ-SYS-107: Create Block Definition
The system shall create reusable block definitions with ports and metadata.
- Pattern: Event-driven (WHEN user creates block)
- Verification: Test
- Priority: Must Have
- Source: DDD §6.1.2

## REQ-SYS-108: Update Block Definition
The system shall allow updating block name, kind, stereotype, description, and ports.
- Pattern: Event-driven (WHEN user updates block)
- Verification: Test
- Priority: Must Have
- Source: DDD §6.1.2

## REQ-SYS-109: Update Block Placement
The system shall allow updating block placement properties (position, size, styling) on specific diagrams.
- Pattern: Event-driven (WHEN user moves/resizes block)
- Verification: Test
- Priority: Must Have
- Source: DDD §6.1.2

## REQ-SYS-110: Create Baseline
The system shall create immutable baseline snapshots of requirements at a point in time.
- Pattern: Event-driven (WHEN user creates baseline)
- Verification: Test
- Priority: Must Have
- Source: DDD §2.3.1, §6.1.2

## REQ-SYS-111: Baseline Reference Generation
The system shall generate unique baseline references in the format BASE-<KEY>-<NNN>.
- Pattern: Event-driven (WHEN baseline created)
- Verification: Test
- Priority: Must Have
- Source: DDD §5.1.1

## REQ-SYS-112: Baseline Metadata
The system shall store author, label, and requirementRefs array for each baseline.
- Pattern: Ubiquitous
- Verification: Test
- Priority: Must Have
- Source: DDD §5.1.1

## REQ-SYS-113: Baseline Snapshots
The system shall create SNAPSHOT_OF relationships from baselines to requirements.
- Pattern: Event-driven (WHEN baseline created)
- Verification: Test
- Priority: Must Have
- Source: DDD §5.1.2

## REQ-SYS-114: List Baselines
The system shall retrieve all baselines for a tenant and project.
- Pattern: Ubiquitous
- Verification: Test
- Priority: Must Have
- Source: DDD §6.1.2

## REQ-SYS-115: Get Baseline Details
The system shall retrieve baseline details including all snapshotted requirements by reference.
- Pattern: Event-driven (WHEN user views baseline)
- Verification: Test
- Priority: Must Have
- Source: DDD §6.1.2

## REQ-SYS-116: Baseline Comparison
The system shall support baseline comparisons and diffs.
- Pattern: Event-driven (WHEN user compares baselines)
- Verification: Test
- Priority: Should Have
- Source: DDD §10.1

## REQ-SYS-117: Git File Tracking
The system shall store markdown requirements in git-friendly format for version control.
- Pattern: Ubiquitous
- Verification: Inspection
- Priority: Should Have
- Source: DDD §5.2, §8.5, §9.1

## REQ-SYS-118: Create Activity Records
The system shall create Activity nodes for all significant system events and user actions.
- Pattern: Event-driven (WHEN action occurs)
- Verification: Test
- Priority: Must Have
- Source: DDD §2.3.7, §5.1.1

## REQ-SYS-119: Activity Type Classification
The system shall classify activities with types including requirement.created, requirement.updated, requirement.archived, requirement.deleted, baseline.created, document.created, diagram.updated, project.created.
- Pattern: Ubiquitous
- Verification: Test
- Priority: Must Have
- Source: DDD §5.1.1

## REQ-SYS-120: Activity Actor Tracking
The system shall record the actor (user email or "system") for each activity.
- Pattern: Ubiquitous
- Verification: Test
- Priority: Must Have
- Source: DDD §5.1.1

## REQ-SYS-121: Activity Timestamp
The system shall record the exact timestamp for each activity event.
- Pattern: Ubiquitous
- Verification: Test
- Priority: Must Have
- Source: DDD §5.1.1

## REQ-SYS-122: Activity Entity Linking
The system shall link activities to affected entities with entityType, entityId, and entityRef.
- Pattern: Ubiquitous
- Verification: Test
- Priority: Must Have
- Source: DDD §5.1.1

## REQ-SYS-123: Activity Metadata Storage
The system shall store activity-specific metadata including changes, old/new values as JSON.
- Pattern: Ubiquitous
- Verification: Test
- Priority: Should Have
- Source: DDD §5.1.1, §6.1.2

## REQ-SYS-124: Tenant-Wide Activity Feed
The system shall provide a tenant-wide activity feed showing all project changes.
- Pattern: Event-driven (WHEN user views feed)
- Verification: Test
- Priority: Must Have
- Source: DDD §2.3.7, §6.1.2

## REQ-SYS-125: Project-Specific Activity Feed
The system shall provide project-specific activity feeds filtered by projectKey.
- Pattern: Event-driven (WHEN user views project activity)
- Verification: Test
- Priority: Must Have
- Source: DDD §2.3.7, §6.1.2

## REQ-SYS-126: User-Specific Activity Feed
The system shall provide user-specific activity history filtered by userId.
- Pattern: Event-driven (WHEN user views own activity)
- Verification: Test
- Priority: Should Have
- Source: DDD §6.1.2

## REQ-SYS-127: Activity Filtering
The system shall support filtering activities by type, date range, and entity.
- Pattern: Event-driven (WHEN user filters feed)
- Verification: Test
- Priority: Should Have
- Source: DDD §2.3.7, §6.1.2

## REQ-SYS-128: Real-Time Activity Updates
The system shall display real-time activity updates for project changes.
- Pattern: Event-driven (WHEN changes occur)
- Verification: Demonstration
- Priority: Could Have
- Source: DDD §2.3.7

## REQ-SYS-129: Collaboration Visibility
The system shall provide visibility of team member actions across projects.
- Pattern: Ubiquitous
- Verification: Demonstration
- Priority: Should Have
- Source: DDD §2.3.7

## REQ-SYS-130: Activity Index Performance
The system shall index activities by timestamp, tenant/project, and entity for fast querying.
- Pattern: Ubiquitous
- Verification: Test
- Priority: Must Have
- Source: DDD §5.1.3

## REQ-SYS-131: Freemium Model Support
The system shall support subscription tiers: free, pro, and enterprise.
- Pattern: Ubiquitous
- Verification: Test
- Priority: Must Have
- Source: DDD §2.3.8, §8.1

## REQ-SYS-132: Stripe Integration
The system shall integrate with Stripe for payment processing.
- Pattern: Event-driven (WHEN payment processed)
- Verification: Test
- Priority: Must Have
- Source: DDD §2.3.8, §6.1.2

## REQ-SYS-133: Subscription Status Tracking
The system shall track subscription status: active, trialing, past_due, canceled, incomplete.
- Pattern: Ubiquitous
- Verification: Test
- Priority: Must Have
- Source: DDD §5.1.1, §6.1.2

## REQ-SYS-134: One Subscription Per Tenant
The system shall enforce one subscription per tenant.
- Pattern: Ubiquitous
- Verification: Test
- Priority: Must Have
- Source: DDD §5.1.1, §5.1.3

## REQ-SYS-135: Stripe Customer Mapping
The system shall store stripeCustomerId and stripeSubscriptionId for each tenant subscription.
- Pattern: Ubiquitous
- Verification: Test
- Priority: Must Have
- Source: DDD §5.1.1

## REQ-SYS-136: Billing Period Tracking
The system shall track currentPeriodStart and currentPeriodEnd for subscriptions.
- Pattern: Ubiquitous
- Verification: Test
- Priority: Must Have
- Source: DDD §5.1.1

## REQ-SYS-137: Trial Period Support
The system shall support trial periods with trialEnd timestamps.
- Pattern: State-driven (WHILE in trial)
- Verification: Test
- Priority: Should Have
- Source: DDD §5.1.1

## REQ-SYS-138: Cancel at Period End
The system shall support cancelAtPeriodEnd flag for graceful subscription cancellation.
- Pattern: State-driven (WHILE cancellation pending)
- Verification: Test
- Priority: Must Have
- Source: DDD §5.1.1

## REQ-SYS-139: Usage Tracking - Projects
The system shall track the number of projects used per tenant.
- Pattern: Event-driven (WHEN project created/deleted)
- Verification: Test
- Priority: Must Have
- Source: DDD §5.1.1, §6.1.2

## REQ-SYS-140: Usage Tracking - Users
The system shall track the number of users per tenant.
- Pattern: Event-driven (WHEN user added/removed)
- Verification: Test
- Priority: Must Have
- Source: DDD §5.1.1, §6.1.2

## REQ-SYS-141: Usage Tracking - Requirements
The system shall track the total number of requirements per tenant.
- Pattern: Event-driven (WHEN requirement created/deleted)
- Verification: Test
- Priority: Must Have
- Source: DDD §5.1.1, §6.1.2

## REQ-SYS-142: Usage Tracking - AI Drafts
The system shall track AI drafts generated per month per tenant.
- Pattern: Event-driven (WHEN AI draft generated)
- Verification: Test
- Priority: Must Have
- Source: DDD §5.1.1, §6.1.2

## REQ-SYS-143: Usage Limit Enforcement
The system shall enforce usage limits based on subscription tier.
- Pattern: Event-driven (WHEN limit exceeded)
- Verification: Test
- Priority: Must Have
- Source: DDD §2.3.8, §6.1.2

## REQ-SYS-144: Unlimited Tier Resources
The system shall represent unlimited tier limits as null values.
- Pattern: Ubiquitous
- Verification: Test
- Priority: Must Have
- Source: DDD §6.1.2

## REQ-SYS-145: Checkout Session Creation
The system shall create Stripe checkout sessions for subscription upgrades.
- Pattern: Event-driven (WHEN user upgrades)
- Verification: Test
- Priority: Must Have
- Source: DDD §6.1.2

## REQ-SYS-146: Customer Portal Access
The system shall create Stripe customer portal sessions for self-service subscription management.
- Pattern: Event-driven (WHEN user accesses portal)
- Verification: Test
- Priority: Must Have
- Source: DDD §2.3.8, §6.1.2

## REQ-SYS-147: Invoice Storage
The system shall store invoice records with Stripe invoice data.
- Pattern: Event-driven (WHEN invoice created)
- Verification: Test
- Priority: Must Have
- Source: DDD §5.1.1, §6.1.2

## REQ-SYS-148: Invoice Metadata
The system shall store amountDue, amountPaid, currency, status, hostedInvoiceUrl, and invoicePdf for each invoice.
- Pattern: Ubiquitous
- Verification: Test
- Priority: Must Have
- Source: DDD §5.1.1

## REQ-SYS-149: List Invoices
The system shall retrieve all invoices for a tenant.
- Pattern: Event-driven (WHEN user views invoices)
- Verification: Test
- Priority: Must Have
- Source: DDD §6.1.2

## REQ-SYS-150: Get Current Usage
The system shall provide current usage metrics against subscription limits.
- Pattern: Event-driven (WHEN user views usage)
- Verification: Test
- Priority: Must Have
- Source: DDD §6.1.2

## REQ-SYS-151: Stripe Webhook Handling
The system shall process Stripe webhooks for subscription events (created, updated, deleted, payment succeeded/failed).
- Pattern: Event-driven (WHEN webhook received)
- Verification: Test
- Priority: Must Have
- Source: DDD §6.1.2

## REQ-SYS-152: Billing Analytics
The system shall provide billing analytics and reporting.
- Pattern: Event-driven (WHEN admin views analytics)
- Verification: Demonstration
- Priority: Should Have
- Source: DDD §2.3.8

## REQ-SYS-153: Daily Incremental Backups
The system shall perform automated daily incremental backups at 2:00 AM with 7-day retention.
- Pattern: Event-driven (WHEN scheduled)
- Verification: Test
- Priority: Must Have
- Source: DDD §8.5

## REQ-SYS-154: Weekly Full Backups
The system shall perform automated weekly full backups on Sundays at 3:00 AM with 4 weeks local retention.
- Pattern: Event-driven (WHEN scheduled)
- Verification: Test
- Priority: Must Have
- Source: DDD §8.5

## REQ-SYS-155: Neo4j Database Dumps
The system shall include Neo4j database dumps in backups.
- Pattern: Ubiquitous (in backups)
- Verification: Test
- Priority: Must Have
- Source: DDD §8.5

## REQ-SYS-156: PostgreSQL Database Dumps
The system shall include PostgreSQL database dumps in backups.
- Pattern: Ubiquitous (in backups)
- Verification: Test
- Priority: Must Have
- Source: DDD §8.5

## REQ-SYS-157: Workspace File Archives
The system shall include workspace markdown file archives in backups.
- Pattern: Ubiquitous (in backups)
- Verification: Test
- Priority: Must Have
- Source: DDD §8.5

## REQ-SYS-158: Configuration Backups
The system shall include configuration files in backups.
- Pattern: Ubiquitous (in backups)
- Verification: Test
- Priority: Must Have
- Source: DDD §8.5

## REQ-SYS-159: Docker Volume Snapshots
The system shall include complete Docker volume snapshots in weekly full backups.
- Pattern: Ubiquitous (in weekly backups)
- Verification: Test
- Priority: Must Have
- Source: DDD §8.5

## REQ-SYS-160: Remote Encrypted Backup Upload
The system shall upload weekly backups to S3-compatible remote storage with encryption via restic.
- Pattern: Event-driven (WHEN weekly backup completes)
- Verification: Test
- Priority: Must Have
- Source: DDD §8.5

## REQ-SYS-161: Remote Retention Policy
The system shall retain remote backups for 12 weeks.
- Pattern: Event-driven (WHEN retention applied)
- Verification: Test
- Priority: Must Have
- Source: DDD §8.5

## REQ-SYS-162: S3-Compatible Storage Support
The system shall support remote backup to DigitalOcean Spaces, AWS S3, Backblaze B2, and SFTP.
- Pattern: Ubiquitous
- Verification: Test
- Priority: Should Have
- Source: DDD §8.5

## REQ-SYS-163: Manual Backup Trigger
The system shall provide admin endpoints to trigger manual daily and weekly backups.
- Pattern: Event-driven (WHEN admin triggers)
- Verification: Test
- Priority: Must Have
- Source: DDD §6.1.2

## REQ-SYS-164: List Local Backups
The system shall provide admin endpoints to list local daily and weekly backups.
- Pattern: Event-driven (WHEN admin requests list)
- Verification: Test
- Priority: Must Have
- Source: DDD §6.1.2

## REQ-SYS-165: List Remote Backups
The system shall provide admin endpoints to list restic snapshots from remote storage.
- Pattern: Event-driven (WHEN admin requests list)
- Verification: Test
- Priority: Must Have
- Source: DDD §6.1.2

## REQ-SYS-166: Backup Integrity Verification
The system shall verify backup integrity via admin endpoint.
- Pattern: Event-driven (WHEN verification requested)
- Verification: Test
- Priority: Must Have
- Source: DDD §6.1.2, §8.5

## REQ-SYS-167: Dry-Run Restoration
The system shall support dry-run restoration to validate backups without applying changes.
- Pattern: Event-driven (WHEN dry-run requested)
- Verification: Test
- Priority: Must Have
- Source: DDD §6.1.2, §8.5

## REQ-SYS-168: Backup System Status
The system shall provide aggregate backup system status via admin endpoint.
- Pattern: Event-driven (WHEN status requested)
- Verification: Test
- Priority: Should Have
- Source: DDD §6.1.2

## REQ-SYS-169: Project Backup Export
The system shall allow exporting individual project backups with scoped permissions.
- Pattern: Event-driven (WHEN user exports project)
- Verification: Test
- Priority: Should Have
- Source: DDD §6.1.2

## REQ-SYS-170: Project Backup Import
The system shall allow Super Admins to import/restore project backups.
- Pattern: Event-driven (WHEN admin imports)
- Verification: Test
- Priority: Should Have
- Source: DDD §6.1.2

## REQ-SYS-171: Project Backup Validation
The system shall validate project backup files before import.
- Pattern: Event-driven (WHEN validation requested)
- Verification: Test
- Priority: Must Have
- Source: DDD §6.1.2

## REQ-SYS-172: Project Backup Statistics
The system shall provide project backup statistics via admin endpoint.
- Pattern: Event-driven (WHEN stats requested)
- Verification: Test
- Priority: Should Have
- Source: DDD §6.1.2

## REQ-SYS-173: Project Backup Retention
The system shall apply retention policies to project backups.
- Pattern: Event-driven (WHEN retention applied)
- Verification: Test
- Priority: Should Have
- Source: DDD §6.1.2

## REQ-SYS-174: Content Hash Drift Detection
The system shall use content hashes for real-time drift detection between Neo4j and file system.
- Pattern: Event-driven (WHEN drift detected)
- Verification: Test
- Priority: Should Have
- Source: DDD §8.5

## REQ-SYS-175: Flexible AI Deployment Options
The system shall support cloud AI, self-hosted AI, and disabled AI deployment modes.
- Pattern: Ubiquitous
- Verification: Test
- Priority: Must Have
- Source: DDD §2.3.9, §4.1.3

## REQ-SYS-176: ITAR Compliance Support
The system shall support ITAR-controlled defense projects via self-hosted LLM mode.
- Pattern: State-driven (WHILE ITAR required)
- Verification: Analysis
- Priority: Must Have
- Source: DDD §4.1.3

## REQ-SYS-177: HIPAA Compliance Support
The system shall support HIPAA compliance via self-hosted LLM mode without BAA.
- Pattern: State-driven (WHILE HIPAA required)
- Verification: Analysis
- Priority: Should Have
- Source: DDD §4.1.3

## REQ-SYS-178: Classified Environment Support
The system shall support classified and air-gapped environments via disabled AI mode.
- Pattern: State-driven (WHILE classified)
- Verification: Analysis
- Priority: Should Have
- Source: DDD §4.1.3

## REQ-SYS-179: Data Sovereignty Control
The system shall ensure data never leaves customer infrastructure in self-hosted AI mode.
- Pattern: State-driven (WHILE self-hosted)
- Verification: Analysis
- Priority: Must Have
- Source: DDD §2.3.9, §4.1.3

## REQ-SYS-180: Per-Project AI Enablement
The system shall support per-project AI enablement settings for compliance.
- Pattern: State-driven (WHILE project restricts AI)
- Verification: Test
- Priority: Should Have
- Source: DDD §2.3.9

## REQ-SYS-181: AI Usage Audit Trail
The system shall maintain comprehensive audit logs for all AI usage including provider, model, and timestamp.
- Pattern: Event-driven (WHEN AI used)
- Verification: Test
- Priority: Must Have
- Source: DDD §2.3.9, §4.1.3

## REQ-SYS-182: Automotive NDA Compliance
The system shall support automotive NDA requirements via self-hosted AI mode.
- Pattern: State-driven (WHILE NDA required)
- Verification: Analysis
- Priority: Should Have
- Source: DDD §4.1.3

## REQ-SYS-183: Tenant Isolation
The system shall enforce complete data isolation between tenants.
- Pattern: Ubiquitous
- Verification: Test
- Priority: Must Have
- Source: DDD §1.3, §2.1, §7.2

## REQ-SYS-184: Tenant Slug Uniqueness
The system shall enforce unique tenant slugs via database constraint.
- Pattern: Ubiquitous
- Verification: Test
- Priority: Must Have
- Source: DDD §5.1.1, §5.1.3

## REQ-SYS-185: Tenant Ownership Validation
The system shall validate tenant ownership before data access on all requests.
- Pattern: Ubiquitous
- Verification: Test
- Priority: Must Have
- Source: DDD §7.2

## REQ-SYS-186: Tenant-Filtered Queries
The system shall filter all database queries by tenant context.
- Pattern: Ubiquitous
- Verification: Test
- Priority: Must Have
- Source: DDD §7.2

## REQ-SYS-187: Project Uniqueness Per Tenant
The system shall enforce unique project slugs within each tenant via composite constraint.
- Pattern: Ubiquitous
- Verification: Test
- Priority: Must Have
- Source: DDD §5.1.3

## REQ-SYS-188: Tenant Creation
The system shall create Tenant nodes with slug, name, and createdAt properties.
- Pattern: Event-driven (WHEN tenant created)
- Verification: Test
- Priority: Must Have
- Source: DDD §5.1.1

## REQ-SYS-189: Workspace Directory Isolation
The system shall isolate workspace files by tenant in workspace/<tenant>/ directories.
- Pattern: Ubiquitous
- Verification: Inspection
- Priority: Must Have
- Source: DDD §4.1.4, §5.2

## REQ-SYS-190: Create Project
The system shall create projects with slug, tenantSlug, and optional key properties.
- Pattern: Event-driven (WHEN project created)
- Verification: Test
- Priority: Must Have
- Source: DDD §5.1.1

## REQ-SYS-191: Project Key Assignment
The system shall support optional short codes (keys) for projects used in requirement references.
- Pattern: Ubiquitous
- Verification: Test
- Priority: Should Have
- Source: DDD §5.1.1

## REQ-SYS-192: Project-Tenant Association
The system shall associate projects with tenants via OWNS relationships.
- Pattern: Ubiquitous
- Verification: Test
- Priority: Must Have
- Source: DDD §5.1.2

## REQ-SYS-193: Project Workspace Structure
The system shall create workspace/<tenant>/<project>/ directory structures for markdown files.
- Pattern: Event-driven (WHEN project created)
- Verification: Inspection
- Priority: Must Have
- Source: DDD §4.1.4, §5.2

## REQ-SYS-194: API Response Time
The system shall maintain API response times below 200ms at the 95th percentile.
- Pattern: Ubiquitous
- Verification: Test
- Priority: Should Have
- Source: DDD §10.2

## REQ-SYS-195: Diagram Rendering Performance
The system shall render diagrams with 100 nodes in less than 1 second.
- Pattern: Event-driven (WHEN diagram rendered)
- Verification: Test
- Priority: Should Have
- Source: DDD §10.2

## REQ-SYS-196: Search Latency
The system shall return search results for 10,000 requirements in less than 500ms.
- Pattern: Event-driven (WHEN search executed)
- Verification: Test
- Priority: Should Have
- Source: DDD §10.2

## REQ-SYS-197: Horizontal Scaling Support
The system shall support horizontal scaling by adding multiple stateless API instances behind a load balancer.
- Pattern: Ubiquitous
- Verification: Test
- Priority: Should Have
- Source: DDD §2.1, §10.2

## REQ-SYS-198: Database Index Performance
The system shall create indexes on frequently queried fields for optimal performance.
- Pattern: Ubiquitous
- Verification: Inspection
- Priority: Must Have
- Source: DDD §5.1.3

## REQ-SYS-199: HTTPS Encryption
The system shall enforce HTTPS for all client-server communication via Traefik TLS termination.
- Pattern: Ubiquitous
- Verification: Test
- Priority: Must Have
- Source: DDD §7.3, §8.2

## REQ-SYS-200: Let's Encrypt Certificates
The system shall automatically obtain and renew TLS certificates via Let's Encrypt.
- Pattern: Event-driven (WHEN certificate expires)
- Verification: Test
- Priority: Must Have
- Source: DDD §8.2, §8.4

## REQ-SYS-201: Neo4j Encrypted Connections
The system shall use encrypted Bolt protocol connections to Neo4j.
- Pattern: Ubiquitous
- Verification: Test
- Priority: Should Have
- Source: DDD §7.3

## REQ-SYS-202: Environment Variable Secrets
The system shall store secrets exclusively in environment variables, never in code.
- Pattern: Ubiquitous
- Verification: Inspection
- Priority: Must Have
- Source: DDD §7.3

## REQ-SYS-203: File System Permissions
The system shall set OS-level file permissions to 600 for sensitive markdown files.
- Pattern: Ubiquitous
- Verification: Test
- Priority: Should Have
- Source: DDD §7.3

## REQ-SYS-204: Input Validation - Backend
The system shall validate all API inputs using Zod schemas for runtime type validation.
- Pattern: Ubiquitous
- Verification: Test
- Priority: Must Have
- Source: DDD §7.4

## REQ-SYS-205: Input Sanitization
The system shall sanitize inputs to prevent HTML and SQL injection attacks.
- Pattern: Ubiquitous
- Verification: Test
- Priority: Must Have
- Source: DDD §7.4

## REQ-SYS-206: Request Schema Validation
The system shall validate request and response schemas using Fastify schema validation.
- Pattern: Ubiquitous
- Verification: Test
- Priority: Must Have
- Source: DDD §7.4

## REQ-SYS-207: Frontend Input Validation
The system shall implement HTML5 form validation and real-time validation feedback.
- Pattern: Event-driven (WHEN user inputs data)
- Verification: Test
- Priority: Should Have
- Source: DDD §7.4

## REQ-SYS-208: Rich Text Sanitization
The system shall sanitize rich text content using DOMPurify.
- Pattern: Event-driven (WHEN rich text rendered)
- Verification: Test
- Priority: Must Have
- Source: DDD §7.4

## REQ-SYS-209: Rate Limiting - Draft Endpoints
The system shall rate limit /api/draft and /api/airgen/chat endpoints to 10 requests per minute per user.
- Pattern: Ubiquitous (for draft endpoints)
- Verification: Test
- Priority: Must Have
- Source: DDD §7.5

## REQ-SYS-210: Rate Limit Response
The system shall return 429 Too Many Requests when rate limits are exceeded.
- Pattern: Event-driven (WHEN limit exceeded)
- Verification: Test
- Priority: Must Have
- Source: DDD §7.5

## REQ-SYS-211: Redis-Based Rate Limiting
The system shall implement rate limiting using Redis when available.
- Pattern: State-driven (WHILE Redis available)
- Verification: Test
- Priority: Should Have
- Source: DDD §7.5

## REQ-SYS-212: Security Headers
The system shall set security headers using Helmet.js middleware.
- Pattern: Ubiquitous
- Verification: Test
- Priority: Must Have
- Source: DDD §7.6

## REQ-SYS-213: Dependency Vulnerability Scanning
The system shall scan dependencies for vulnerabilities using npm audit and Snyk.
- Pattern: Event-driven (WHEN dependencies updated)
- Verification: Test
- Priority: Should Have
- Source: DDD §7.6

## REQ-SYS-214: TypeScript Strict Mode
The system shall use TypeScript strict mode to prevent type errors.
- Pattern: Ubiquitous
- Verification: Inspection
- Priority: Must Have
- Source: DDD §7.6

## REQ-SYS-215: ESLint Security Rules
The system shall enforce ESLint security rules during development.
- Pattern: Ubiquitous
- Verification: Inspection
- Priority: Should Have
- Source: DDD §7.6

## REQ-SYS-216: Principle of Least Privilege
The system shall enforce the principle of least privilege for user permissions.
- Pattern: Ubiquitous
- Verification: Analysis
- Priority: Must Have
- Source: DDD §7.6

## REQ-SYS-217: Regular Security Audits
The system shall undergo regular security audits.
- Pattern: Event-driven (WHEN audit scheduled)
- Verification: Inspection
- Priority: Should Have
- Source: DDD §7.6

## REQ-SYS-218: Automated Dependency Updates
The system shall use Dependabot for automated dependency updates.
- Pattern: Event-driven (WHEN dependencies outdated)
- Verification: Inspection
- Priority: Should Have
- Source: DDD §7.6

## REQ-SYS-219: Stateless API Design
The system shall implement stateless API servers for horizontal scaling.
- Pattern: Ubiquitous
- Verification: Analysis
- Priority: Must Have
- Source: DDD §2.1, §10.2

## REQ-SYS-220: Neo4j Causal Cluster Support
The system shall support Neo4j causal clustering for high availability at scale.
- Pattern: State-driven (WHILE at scale)
- Verification: Test
- Priority: Could Have
- Source: DDD §10.2

## REQ-SYS-221: Redis Cluster Support
The system shall support Redis clustering for distributed caching.
- Pattern: State-driven (WHILE at scale)
- Verification: Test
- Priority: Could Have
- Source: DDD §10.2

## REQ-SYS-222: CDN Static Asset Delivery
The system shall support CDN delivery for frontend static assets.
- Pattern: State-driven (WHILE at scale)
- Verification: Test
- Priority: Could Have
- Source: DDD §10.2

## REQ-SYS-223: Load Balancer Support
The system shall support deployment behind load balancers for traffic distribution.
- Pattern: State-driven (WHILE at scale)
- Verification: Test
- Priority: Should Have
- Source: DDD §10.2

## REQ-SYS-224: Concurrent User Support
The system shall support 1-50 concurrent users in current scale, scaling to 100-1,000 users.
- Pattern: Ubiquitous
- Verification: Test
- Priority: Should Have
- Source: DDD §10.2

## REQ-SYS-225: Requirements Scale Support
The system shall support 1,000-10,000 requirements per project, scaling to 100,000+.
- Pattern: Ubiquitous
- Verification: Test
- Priority: Should Have
- Source: DDD §10.2

## REQ-SYS-226: Multi-Tenant Scale Support
The system shall support 1-10 tenants currently, scaling to 100+ tenants.
- Pattern: Ubiquitous
- Verification: Test
- Priority: Should Have
- Source: DDD §10.2

## REQ-SYS-227: SaaS Uptime SLA
The system shall maintain 99.9% uptime SLA for SaaS deployments.
- Pattern: Ubiquitous (for SaaS)
- Verification: Test
- Priority: Must Have
- Source: DDD §8.1

## REQ-SYS-228: Automatic Security Updates
The system shall apply automatic security patches for SaaS deployments.
- Pattern: Event-driven (WHEN patch available)
- Verification: Test
- Priority: Must Have
- Source: DDD §8.1

## REQ-SYS-229: Health Check Endpoint
The system shall provide /api/health endpoint for monitoring system health.
- Pattern: Event-driven (WHEN checked)
- Verification: Test
- Priority: Must Have
- Source: DDD §6.1.2, §8.6

## REQ-SYS-230: Docker Health Checks
The system shall implement Docker healthcheck commands in Compose file.
- Pattern: Event-driven (WHEN checked)
- Verification: Test
- Priority: Must Have
- Source: DDD §8.6

## REQ-SYS-231: Prometheus Metrics
The system shall expose /metrics endpoint for Prometheus scraping.
- Pattern: Event-driven (WHEN scraped)
- Verification: Test
- Priority: Should Have
- Source: DDD §6.1.2, §8.6

## REQ-SYS-232: Grafana Dashboards
The system shall support Grafana dashboards for metrics visualization.
- Pattern: Ubiquitous
- Verification: Demonstration
- Priority: Should Have
- Source: DDD §8.6

## REQ-SYS-233: Alertmanager Notifications
The system shall support Alertmanager for operational notifications.
- Pattern: Event-driven (WHEN alert triggered)
- Verification: Test
- Priority: Should Have
- Source: DDD §8.6

## REQ-SYS-234: Sentry Error Tracking
The system shall send backend exceptions to Sentry for error tracking.
- Pattern: Event-driven (WHEN error occurs)
- Verification: Test
- Priority: Should Have
- Source: DDD §8.6

## REQ-SYS-235: Frontend Error Tracking
The system shall send frontend errors to Sentry via SDK with user context.
- Pattern: Event-driven (WHEN error occurs)
- Verification: Test
- Priority: Should Have
- Source: DDD §8.6

## REQ-SYS-236: Structured Logging
The system shall output Fastify JSON logs to stdout for aggregation.
- Pattern: Ubiquitous
- Verification: Inspection
- Priority: Must Have
- Source: DDD §8.6

## REQ-SYS-237: Docker Log Aggregation
The system shall aggregate Docker logs for centralized analysis.
- Pattern: Ubiquitous
- Verification: Test
- Priority: Should Have
- Source: DDD §8.6

## REQ-SYS-238: Log Rotation
The system shall rotate logs via Docker daemon configuration.
- Pattern: Event-driven (WHEN rotation triggered)
- Verification: Test
- Priority: Should Have
- Source: DDD §8.6

## REQ-SYS-239: Single Page Application
The system shall provide a React-based single page application for the user interface.
- Pattern: Ubiquitous
- Verification: Demonstration
- Priority: Must Have
- Source: DDD §2.1, §3.2.2

## REQ-SYS-240: React Router Navigation
The system shall use React Router v6 for client-side navigation.
- Pattern: Ubiquitous
- Verification: Test
- Priority: Must Have
- Source: DDD §3.2.2

## REQ-SYS-241: Markdown Preview
The system shall provide live markdown preview during requirement editing.
- Pattern: State-driven (WHILE editing)
- Verification: Demonstration
- Priority: Should Have
- Source: DDD §4.2.3

## REQ-SYS-242: Monaco Editor Integration
The system shall integrate Monaco Editor (VS Code engine) for markdown editing.
- Pattern: Ubiquitous (in editors)
- Verification: Test
- Priority: Should Have
- Source: DDD §4.2.3

## REQ-SYS-243: Syntax Highlighting
The system shall provide syntax highlighting for markdown content.
- Pattern: Ubiquitous (in editors)
- Verification: Demonstration
- Priority: Should Have
- Source: DDD §4.2.3

## REQ-SYS-244: Keyboard Shortcuts
The system shall support keyboard shortcuts in editors.
- Pattern: Event-driven (WHEN shortcut pressed)
- Verification: Test
- Priority: Should Have
- Source: DDD §4.2.3

## REQ-SYS-245: Undo/Redo Support
The system shall provide undo/redo functionality in editors.
- Pattern: Event-driven (WHEN user undoes/redoes)
- Verification: Test
- Priority: Must Have
- Source: DDD §4.2.3

## REQ-SYS-246: Search/Replace
The system shall provide search and replace functionality in editors.
- Pattern: Event-driven (WHEN user searches)
- Verification: Test
- Priority: Should Have
- Source: DDD §4.2.3

## REQ-SYS-247: Theme Support
The system shall support light and dark themes in editors.
- Pattern: State-driven (WHILE theme selected)
- Verification: Demonstration
- Priority: Should Have
- Source: DDD §4.2.3

## REQ-SYS-248: Toast Notifications
The system shall display toast notifications for user actions and errors.
- Pattern: Event-driven (WHEN notification triggered)
- Verification: Demonstration
- Priority: Must Have
- Source: DDD §4.2.4

## REQ-SYS-249: User-Friendly Error Messages
The system shall display user-friendly error messages for API errors.
- Pattern: Event-driven (WHEN error occurs)
- Verification: Demonstration
- Priority: Must Have
- Source: DDD §4.2.4

## REQ-SYS-250: Automatic Token Refresh UI
The system shall automatically retry requests after token refresh without user intervention.
- Pattern: Event-driven (WHEN token expires)
- Verification: Test
- Priority: Must Have
- Source: DDD §4.2.4

## REQ-SYS-251: Loading States
The system shall display loading states during asynchronous operations.
- Pattern: State-driven (WHILE loading)
- Verification: Demonstration
- Priority: Must Have
- Source: DDD §3.2.2

## REQ-SYS-252: Optimistic Updates
The system shall implement optimistic UI updates for better user experience.
- Pattern: Event-driven (WHEN user action)
- Verification: Demonstration
- Priority: Should Have
- Source: DDD §9.5

## REQ-SYS-253: Modular Monolith Architecture
The system shall organize code as a modular monolith with logically separated components.
- Pattern: Ubiquitous
- Verification: Inspection
- Priority: Must Have
- Source: DDD §2.1, §3.1

## REQ-SYS-254: TypeScript Strict Mode
The system shall use TypeScript with strict mode enabled.
- Pattern: Ubiquitous
- Verification: Inspection
- Priority: Must Have
- Source: DDD §3.2.1, §3.2.2

## REQ-SYS-255: ES Modules
The system shall use ES Modules for the module system.
- Pattern: Ubiquitous
- Verification: Inspection
- Priority: Must Have
- Source: DDD §3.2.1

## REQ-SYS-256: Pnpm Workspaces
The system shall use pnpm workspaces for monorepo management.
- Pattern: Ubiquitous
- Verification: Inspection
- Priority: Must Have
- Source: DDD §9.4

## REQ-SYS-257: Shared QA Library
The system shall maintain a shared req-qa library package for QA rules.
- Pattern: Ubiquitous
- Verification: Inspection
- Priority: Must Have
- Source: DDD §3.2.3, §9.4

## REQ-SYS-258: Repository Pattern
The system shall use repository pattern for abstracting Neo4j queries.
- Pattern: Ubiquitous
- Verification: Inspection
- Priority: Must Have
- Source: DDD §3.2.1, §4.1.2

## REQ-SYS-259: Factory Pattern
The system shall use factory pattern for creating LLM provider instances.
- Pattern: Ubiquitous
- Verification: Inspection
- Priority: Must Have
- Source: DDD §3.2.1

## REQ-SYS-260: Component Composition
The system shall use small, composable React components.
- Pattern: Ubiquitous
- Verification: Inspection
- Priority: Must Have
- Source: DDD §3.2.2

## REQ-SYS-261: Custom React Hooks
The system shall encapsulate state logic in custom React hooks.
- Pattern: Ubiquitous
- Verification: Inspection
- Priority: Must Have
- Source: DDD §3.2.2

## REQ-SYS-262: Context Providers
The system shall use context providers for scoped global state.
- Pattern: Ubiquitous
- Verification: Inspection
- Priority: Must Have
- Source: DDD §3.2.2

## REQ-SYS-263: ISO 29148 Standard Support
The system shall support ISO/IEC/IEEE 29148 requirements engineering standards.
- Pattern: Ubiquitous
- Verification: Analysis
- Priority: Must Have
- Source: DDD §1.1, §1.3, §3.2.3

## REQ-SYS-264: EARS Pattern Support
The system shall support Easy Approach to Requirements Syntax (EARS) patterns.
- Pattern: Ubiquitous
- Verification: Test
- Priority: Must Have
- Source: DDD §3.2.3, Appendix A, B

## REQ-SYS-265: Audit Trail Completeness
The system shall maintain complete audit trails for all requirement changes.
- Pattern: Ubiquitous
- Verification: Test
- Priority: Must Have
- Source: DDD §2.3.1, §7.6

## REQ-SYS-266: Compliance Package Support
The system shall support pre-built compliance templates for ISO 26262, DO-178C.
- Pattern: Optional
- Verification: Demonstration
- Priority: Could Have
- Source: DDD §10.1

## REQ-SYS-267: SaaS Deployment Support
The system shall support SaaS deployment at airgen.studio with zero infrastructure management.
- Pattern: Ubiquitous (for SaaS)
- Verification: Demonstration
- Priority: Must Have
- Source: DDD §1.3, §8.1

## REQ-SYS-268: Self-Hosted VPS Deployment
The system shall support self-hosted deployment on VPS via Docker Compose.
- Pattern: Ubiquitous (for self-hosted)
- Verification: Test
- Priority: Must Have
- Source: DDD §8.1

## REQ-SYS-269: Managed Hosting Support
The system shall support managed enterprise hosting on customer infrastructure.
- Pattern: Ubiquitous (for enterprise)
- Verification: Demonstration
- Priority: Should Have
- Source: DDD §8.1

## REQ-SYS-270: Development Environment Setup
The system shall provide local development environment with Docker Compose and hot-reload.
- Pattern: Ubiquitous (for dev)
- Verification: Test
- Priority: Must Have
- Source: DDD §8.1

## REQ-SYS-271: Staging Environment Support
The system shall support staging environments with isolated workspace directories.
- Pattern: Ubiquitous (for staging)
- Verification: Test
- Priority: Should Have
- Source: DDD §8.1

## REQ-SYS-272: Docker Compose Deployment
The system shall deploy via Docker Compose with Traefik, API, Neo4j, and Redis services.
- Pattern: Ubiquitous
- Verification: Test
- Priority: Must Have
- Source: DDD §8.2

## REQ-SYS-273: Persistent Volume Management
The system shall manage persistent volumes for Neo4j data, Redis data, workspace files, and TLS certificates.
- Pattern: Ubiquitous
- Verification: Test
- Priority: Must Have
- Source: DDD §8.2

## REQ-SYS-274: Environment Configuration
The system shall configure environments via .env files for development and production.
- Pattern: Ubiquitous
- Verification: Test
- Priority: Must Have
- Source: DDD §8.4

## REQ-SYS-275: Deployment Rollback Support
The system shall support deployment rollback via git revert and rebuild.
- Pattern: Event-driven (WHEN rollback needed)
- Verification: Test
- Priority: Must Have
- Source: DDD §8.4

## REQ-SYS-276: REST API Interface
The system shall provide RESTful API with resource-oriented URLs and JSON payloads.
- Pattern: Ubiquitous
- Verification: Test
- Priority: Must Have
- Source: DDD §6.1.1

## REQ-SYS-277: Consistent Error Format
The system shall return errors in consistent JSON format with error, message, statusCode, and details fields.
- Pattern: Ubiquitous (for errors)
- Verification: Test
- Priority: Must Have
- Source: DDD §6.1.1

## REQ-SYS-278: API Versioning Support
The system shall support API versioning for future compatibility (implicit v1, future /api/v2).
- Pattern: Ubiquitous
- Verification: Analysis
- Priority: Should Have
- Source: DDD §6.1.1

## REQ-SYS-279: CORS Support
The system shall support CORS for cross-origin API requests.
- Pattern: Ubiquitous
- Verification: Test
- Priority: Must Have
- Source: DDD §3.2.1

## REQ-SYS-280: WebSocket Support (Future)
The system shall support WebSocket connections for real-time collaboration features.
- Pattern: Optional
- Verification: Test
- Priority: Could Have
- Source: DDD §6.3, §10.1

## REQ-SYS-281: External Integration Hub
The system shall support integrations with Jira, GitHub, and Azure DevOps.
- Pattern: Optional
- Verification: Test
- Priority: Could Have
- Source: DDD §10.1

## REQ-SYS-282: Email Notification Integration
The system shall integrate with Resend for transactional email notifications.
- Pattern: Event-driven (WHEN notification sent)
- Verification: Test
- Priority: Should Have
- Source: DDD §2.2

## REQ-SYS-283: Git Repository Integration
The system shall support git repository integration for markdown file tracking.
- Pattern: Ubiquitous
- Verification: Test
- Priority: Should Have
- Source: DDD §2.2

## REQ-SYS-284: Vector Search
The system shall support semantic similarity search using vector embeddings (pgvector or Qdrant).
- Pattern: Optional
- Verification: Test
- Priority: Could Have
- Source: DDD §10.1

## REQ-SYS-285: Collaborative Editing
The system shall support WebSocket-based real-time collaborative editing.
- Pattern: Optional
- Verification: Demonstration
- Priority: Could Have
- Source: DDD §10.1

## REQ-SYS-286: Comment System
The system shall support inline comments on requirements.
- Pattern: Optional
- Verification: Test
- Priority: Could Have
- Source: DDD §10.1

## REQ-SYS-287: Email/Slack Notifications
The system shall send email and Slack notifications for requirement changes.
- Pattern: Optional
- Verification: Test
- Priority: Could Have
- Source: DDD §10.1

## REQ-SYS-288: Export to Word/PDF
The system shall generate Word and PDF reports from requirements.
- Pattern: Optional
- Verification: Test
- Priority: Could Have
- Source: DDD §10.1

## REQ-SYS-289: Mobile Application
The system shall provide a React Native mobile companion app.
- Pattern: Optional
- Verification: Demonstration
- Priority: Could Have
- Source: DDD §10.1

## REQ-SYS-290: AI Automatic Traceability
The system shall automatically create trace links using semantic analysis.
- Pattern: Optional
- Verification: Test
- Priority: Could Have
- Source: DDD §10.1

## REQ-SYS-291: Workflow Automation
The system shall support custom approval workflows.
- Pattern: Optional
- Verification: Test
- Priority: Could Have
- Source: DDD §10.1

## REQ-SYS-292: Marketplace Support
The system shall provide a marketplace for user-contributed templates and plugins.
- Pattern: Optional
- Verification: Demonstration
- Priority: Could Have
- Source: DDD §10.1
